# -*- coding: utf-8 -*-
"""
Created on Sat Oct 03 11:22:34 2015

@author: Binoy
"""

import Draft
import FreeCAD


def readOffset(filename= None):
    fname = r"C:\Users\Binoy\Google Drive\Academics\General Pyscripts\Scripts-Intern\Rhino\xpan--200"
    _file = open(fname, 'r')


    hdr = _file.next()

    line = _file.next()             


    _curves = []
    _Cur = []
    while line:                     
        print line                  #

        lstLine = [float(v) for v in line.split()]

        if int(lstLine[-1]) == 1:
            if  _Cur:            #Adding curve to curve list
                _curves.append(_Cur)
                print _Cur
                _Cur = []
                _Cur.append(tuple(lstLine[:-1]))
        else:
            _Cur.append(tuple(lstLine[:-1]))



        line = _file.next()
        if line == "end":
            break
            _file.close()
            

    return _curves

def DrawSpline(dat):
    for l in dat:
        wire = []
        for j in l:
            wire.append(FreeCAD.Vector(j))
        print wire
        Draft.makeBSpline(wire,closed=False,face=False,support=None)
        
    

if __name__ == "__main__":
    DrawSpline(readOffset())
